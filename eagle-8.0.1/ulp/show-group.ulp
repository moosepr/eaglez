#usage "en: <b>Show group from schematic/board in board/schematic</b>"
            "<p>"
            "Select a group of objects in the Schematic and run this ULP "
            "in the Layout editor. All objects belonging to the group will "
            "be highlighted. Works also from Layout to Schematic.<p>"
            "<author>Author: support@cadsoft.de</author>",
       "de: <b>Zeigt ein gewählte Gruppe aus Schaltplan/Board im Board/Schaltplan</b>"
           "<p>"
           "Wählen Sie mit GROUP eine Gruppe von Objekten im Schaltplan "
           "und starten Sie das ULP dann im Layout. Alle entsprechenden "
           "Objekte werden jetzt heller dargestellt. Das funktioniert auch "
           "vom Layout in den Schaltplan."
           "<p>"
           "<author>Autor: support@cadsoft.de</author>"

//History:
// 1.0.0 Initial release 2012-03-28
// 1.0.1 Improved usage  2016-04-29

string Version = "1.0.1";

string Cmd = "SHOW ";
int cnt = 0;

if (schematic) {
  if (project.board) project.board(B) {
    B.elements(E) {
      if (ingroup(E)) {
        Cmd += " " + E.name;
        cnt++;
      }
    }
  }
}

else if (board) {
  if (project.schematic) project.schematic(SCH) {
    SCH.parts(P) {
      P.instances(I) {
        if (ingroup(I)) {
          Cmd += " " + P.name;
          cnt++;
          break;
        }
      }
    }
  }
}

else dlgMessageBox("!Start this ULP in a board or schematic.", "OK");

if(!cnt) {
  dlgMessageBox("!No group selected.", "OK");
}
exit(Cmd);
